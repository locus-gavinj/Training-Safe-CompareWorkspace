FME workspace CompareWorkspace.fmw
Title: SpatialRelationships

Parameters:
- SourceDataset_ACAD = C:\FMETrainingData\Data\Parcels\BuildingFootprints.dwg   # Source Autodesk AutoCAD DWG/DXF File(s)
- SourceDataset_FILEGDB = C:\FMETrainingData\Data\Addresses\Addresses.gdb   # Source Geodatabase

Readers:
- ACAD_2: ACAD from $(SourceDataset_ACAD)
- FILEGDB_1: FILEGDB from $(SourceDataset_FILEGDB)

BuildingFootprints (reader ACAD_2)
    -> SpatialFilter [Filter]
    -> BuildingFootprints
BuildingFootprints: Inspector
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> Passed
    FAILED -> Failed
Passed: Inspector
Failed: Inspector
